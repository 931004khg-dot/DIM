;;;; ============================================================================
;;;; AutoCAD 치수 스타일 생성 LISP 프로그램
;;;; 파일명: dimstyle.lsp
;;;; ============================================================================

(vl-load-com)

(setq *g_dimstyle_lsp_path*
  (if *load-pathname*
    (vl-filename-directory *load-pathname*)
    nil ; 로드 경로를 찾을 수 없음 (예: 붙여넣기 실행)
  )
)

;; 마지막 사용 축척 저장 (전역 변수)
(if (not *last_dim_scale*)
  (setq *last_dim_scale* "20")  ; 기본값: 20
)

;; 마지막 사용 y값 (치수선 거리) 저장 (전역 변수)
(if (not *last_dim_distance*)
  (setq *last_dim_distance* "400")  ; 기본값: 400
)

;; 고급 옵션 저장 (전역 변수)
(if (not *custom_text_height*)
  (setq *custom_text_height* nil)  ; nil = 자동 계산
)
(if (not *custom_arrow_size*)
  (setq *custom_arrow_size* nil)
)
(if (not *custom_ext_offset*)
  (setq *custom_ext_offset* nil)
)
(if (not *custom_ext_extend*)
  (setq *custom_ext_extend* nil)
)
(if (not *custom_text_gap*)
  (setq *custom_text_gap* nil)
)

;;;; ============================================================================
;;;; DCL 파일 생성 함수
;;;; ============================================================================
(defun create_dcl_file (/ dcl_file dcl_path)
  
  (if (and *g_dimstyle_lsp_path* (vl-file-directory-p *g_dimstyle_lsp_path*))
    (setq dcl_path (strcat *g_dimstyle_lsp_path* "\\dimstyle.dcl")) ; 윈도우 경로 구분자 사용
    
    (progn
      (setq dcl_path (vl-filename-mktemp "dimstyle_dcl" nil ".dcl"))
      (princ (strcat "\nLISP 파일 경로를 찾을 수 없어 임시 폴더에 DCL 생성: " dcl_path))
    )
  )
  
  (setq dcl_file (open dcl_path "w"))
  
  (if dcl_file
    (progn
      ;; DCL 내용 작성
      (write-line "// ============================================================================" dcl_file)
      (write-line "// AutoCAD 치수 스타일 DCL 대화상자" dcl_file)
      (write-line "// 자동 생성됨" dcl_file)
      (write-line "// ============================================================================" dcl_file)
      (write-line "" dcl_file)
      (write-line "dimstyle : dialog {" dcl_file)
      (write-line "    label = \"ISO-25 치수 스타일 설정\";" dcl_file)
      (write-line "    " dcl_file)
      (write-line "    : boxed_column {" dcl_file)
      (write-line "        label = \"기본 설정 (ISO-25 표준)\";" dcl_file)
      (write-line "        " dcl_file)
      (write-line "        // 치수 타입 선택" dcl_file)
      (write-line "        : boxed_radio_column {" dcl_file)
      (write-line "            label = \"치수 타입\";" dcl_file)
      (write-line "            : radio_button {" dcl_file)
      (write-line "                key = \"dim_linear\";" dcl_file)
      (write-line "                label = \"회전된 치수 (DIMLINEAR)\";" dcl_file)
      (write-line "            }" dcl_file)
      (write-line "            : radio_button {" dcl_file)
      (write-line "                key = \"dim_aligned\";" dcl_file)
      (write-line "                label = \"정렬된 치수 (DIMALIGNED)\";" dcl_file)
      (write-line "            }" dcl_file)
      (write-line "        }" dcl_file)
      (write-line "        " dcl_file)
      (write-line "        // 전체 축척" dcl_file)
      (write-line "        : row {" dcl_file)
      (write-line "            : text {" dcl_file)
      (write-line "                label = \"전체 축척 (DIMSCALE):\";" dcl_file)
      (write-line "                width = 25;" dcl_file)
      (write-line "                fixed_width = true;" dcl_file)
      (write-line "                alignment = left;" dcl_file)
      (write-line "            }" dcl_file)
      (write-line "            : edit_box {" dcl_file)
      (write-line "                key = \"dimscale\";" dcl_file)
      (write-line "                edit_width = 10;" dcl_file)
      (write-line "                value = \"20\";" dcl_file)
      (write-line "                alignment = left;" dcl_file)
      (write-line "            }" dcl_file)
      (write-line "        }" dcl_file)
      (write-line "        " dcl_file)
      (write-line "        // 치수선 거리 (Y값)" dcl_file)
      (write-line "        : row {" dcl_file)
      (write-line "            : text {" dcl_file)
      (write-line "                label = \"치수선 거리 (Y값):\";" dcl_file)
      (write-line "                width = 25;" dcl_file)
      (write-line "                fixed_width = true;" dcl_file)
      (write-line "                alignment = left;" dcl_file)
      (write-line "            }" dcl_file)
      (write-line "            : text {" dcl_file)
      (write-line "                key = \"dim_distance_display\";" dcl_file)
      (write-line "                width = 10;" dcl_file)
      (write-line "                fixed_width = true;" dcl_file)
      (write-line "                alignment = left;" dcl_file)
      (write-line "            }" dcl_file)
      (write-line "        }" dcl_file)
      (write-line "        " dcl_file)
      (write-line "        // 문자 높이 (자동 계산)" dcl_file)
      (write-line "        : row {" dcl_file)
      (write-line "            : text {" dcl_file)
      (write-line "                label = \"문자 높이 (DIMTXT):\";" dcl_file)
      (write-line "                width = 25;" dcl_file)
      (write-line "                fixed_width = true;" dcl_file)
      (write-line "                alignment = left;" dcl_file)
      (write-line "            }" dcl_file)
      (write-line "            : text {" dcl_file)
      (write-line "                key = \"textheight\";" dcl_file)
      (write-line "                width = 10;" dcl_file)
      (write-line "                fixed_width = true;" dcl_file)
      (write-line "                alignment = left;" dcl_file)
      (write-line "            }" dcl_file)
      (write-line "        }" dcl_file)
      (write-line "        " dcl_file)
      (write-line "        // 화살표 크기 (자동 계산)" dcl_file)
      (write-line "        : row {" dcl_file)
      (write-line "            : text {" dcl_file)
      (write-line "                label = \"화살표 크기 (DIMASZ):\";" dcl_file)
      (write-line "                width = 25;" dcl_file)
      (write-line "                fixed_width = true;" dcl_file)
      (write-line "                alignment = left;" dcl_file)
      (write-line "            }" dcl_file)
      (write-line "            : text {" dcl_file)
      (write-line "                key = \"arrowsize\";" dcl_file)
      (write-line "                width = 10;" dcl_file)
      (write-line "                fixed_width = true;" dcl_file)
      (write-line "                alignment = left;" dcl_file)
      (write-line "            }" dcl_file)
      (write-line "        }" dcl_file)
      (write-line "    }" dcl_file)
      (write-line "    " dcl_file)
      (write-line "    : boxed_column {" dcl_file)
      (write-line "        label = \"치수보조선 설정\";" dcl_file)
      (write-line "        " dcl_file)
      (write-line "        // 치수보조선 간격띄우기 (자동 계산)" dcl_file)
      (write-line "        : row {" dcl_file)
      (write-line "            : text {" dcl_file)
      (write-line "                label = \"간격띄우기 (DIMEXO):\";" dcl_file)
      (write-line "                width = 25;" dcl_file)
      (write-line "                fixed_width = true;" dcl_file)
      (write-line "                alignment = left;" dcl_file)
      (write-line "            }" dcl_file)
      (write-line "            : text {" dcl_file)
      (write-line "                key = \"extoffset\";" dcl_file)
      (write-line "                width = 10;" dcl_file)
      (write-line "                fixed_width = true;" dcl_file)
      (write-line "                alignment = left;" dcl_file)
      (write-line "            }" dcl_file)
      (write-line "        }" dcl_file)
      (write-line "        " dcl_file)
      (write-line "        // 치수보조선 연장 (자동 계산)" dcl_file)
      (write-line "        : row {" dcl_file)
      (write-line "            : text {" dcl_file)
      (write-line "                label = \"보조선 연장 (DIMEXE):\";" dcl_file)
      (write-line "                width = 25;" dcl_file)
      (write-line "                fixed_width = true;" dcl_file)
      (write-line "                alignment = left;" dcl_file)
      (write-line "            }" dcl_file)
      (write-line "            : text {" dcl_file)
      (write-line "                key = \"extextend\";" dcl_file)
      (write-line "                width = 10;" dcl_file)
      (write-line "                fixed_width = true;" dcl_file)
      (write-line "                alignment = left;" dcl_file)
      (write-line "            }" dcl_file)
      (write-line "        }" dcl_file)
      (write-line "    }" dcl_file)
      (write-line "    " dcl_file)
      (write-line "    : boxed_column {" dcl_file)
      (write-line "        label = \"문자 설정\";" dcl_file)
      (write-line "        " dcl_file)
      (write-line "        // 문자와 치수선 간격 (자동 계산)" dcl_file)
      (write-line "        : row {" dcl_file)
      (write-line "            : text {" dcl_file)
      (write-line "                label = \"문자 간격 (DIMGAP):\";" dcl_file)
      (write-line "                width = 25;" dcl_file)
      (write-line "                fixed_width = true;" dcl_file)
      (write-line "                alignment = left;" dcl_file)
      (write-line "            }" dcl_file)
      (write-line "            : text {" dcl_file)
      (write-line "                key = \"textgap\";" dcl_file)
      (write-line "                width = 10;" dcl_file)
      (write-line "                fixed_width = true;" dcl_file)
      (write-line "                alignment = left;" dcl_file)
      (write-line "            }" dcl_file)
      (write-line "        }" dcl_file)
      (write-line "    }" dcl_file)
      (write-line "    " dcl_file)
      (write-line "    spacer;" dcl_file)
      (write-line "    " dcl_file)
      (write-line "    // 버튼" dcl_file)
      (write-line "    : row {" dcl_file)
      (write-line "        : spacer { width = 1; }" dcl_file)
      (write-line "        " dcl_file)
      (write-line "        : button {" dcl_file)
      (write-line "            key = \"create_leader\";" dcl_file)
      (write-line "            label = \"지시선\";" dcl_file)
      (write-line "            fixed_width = true;" dcl_file)
      (write-line "            width = 12;" dcl_file)
      (write-line "        }" dcl_file)
      (write-line "        " dcl_file)
      (write-line "        : button {" dcl_file)
      (write-line "            key = \"edit_advanced\";" dcl_file)
      (write-line "            label = \"설정\";" dcl_file)
      (write-line "            fixed_width = true;" dcl_file)
      (write-line "            width = 12;" dcl_file)
      (write-line "        }" dcl_file)
      (write-line "        " dcl_file)
      (write-line "        : button {" dcl_file)
      (write-line "            key = \"reset\";" dcl_file)
      (write-line "            label = \"리셋\";" dcl_file)
      (write-line "            fixed_width = true;" dcl_file)
      (write-line "            width = 12;" dcl_file)
      (write-line "        }" dcl_file)
      (write-line "        " dcl_file)
      (write-line "        : button {" dcl_file)
      (write-line "            key = \"accept\";" dcl_file)
      (write-line "            label = \"확인\";" dcl_file)
      (write-line "            is_default = true;" dcl_file)
      (write-line "            fixed_width = true;" dcl_file)
      (write-line "            width = 12;" dcl_file)
      (write-line "        }" dcl_file)
      (write-line "        " dcl_file)
      (write-line "        : button {" dcl_file)
      (write-line "            key = \"cancel\";" dcl_file)
      (write-line "            label = \"취소\";" dcl_file)
      (write-line "            is_cancel = true;" dcl_file)
      (write-line "            fixed_width = true;" dcl_file)
      (write-line "            width = 12;" dcl_file)
      (write-line "        }" dcl_file)
      (write-line "        " dcl_file)
      (write-line "        : spacer { width = 1; }" dcl_file)
      (write-line "    }" dcl_file)
      (write-line "}" dcl_file)
      (write-line "" dcl_file)
      (write-line "// ============================================================================" dcl_file)
      (write-line "// 고급 옵션 수정 대화상자" dcl_file)
      (write-line "// ============================================================================" dcl_file)
      (write-line "" dcl_file)
      (write-line "advanced_settings : dialog {" dcl_file)
      (write-line "    label = \"고급 설정\";" dcl_file)
      (write-line "    " dcl_file)
      (write-line "    : boxed_column {" dcl_file)
      (write-line "        label = \"기본 설정\";" dcl_file)
      (write-line "        : row {" dcl_file)
      (write-line "            : text {" dcl_file)
      (write-line "                label = \"치수선 거리 (Y값):\";" dcl_file)
      (write-line "                width = 25;" dcl_file)
      (write-line "            }" dcl_file)
      (write-line "            : edit_box {" dcl_file)
      (write-line "                key = \"adv_distance\";" dcl_file)
      (write-line "                edit_width = 10;" dcl_file)
      (write-line "            }" dcl_file)
      (write-line "        }" dcl_file)
      (write-line "    }" dcl_file)
      (write-line "    " dcl_file)
      (write-line "    : boxed_column {" dcl_file)
      (write-line "        label = \"문자 설정\";" dcl_file)
      (write-line "        : row {" dcl_file)
      (write-line "            : text {" dcl_file)
      (write-line "                label = \"문자 높이 (DIMTXT):\";" dcl_file)
      (write-line "                width = 25;" dcl_file)
      (write-line "            }" dcl_file)
      (write-line "            : edit_box {" dcl_file)
      (write-line "                key = \"adv_textheight\";" dcl_file)
      (write-line "                edit_width = 10;" dcl_file)
      (write-line "            }" dcl_file)
      (write-line "        }" dcl_file)
      (write-line "        : row {" dcl_file)
      (write-line "            : text {" dcl_file)
      (write-line "                label = \"문자 간격 (DIMGAP):\";" dcl_file)
      (write-line "                width = 25;" dcl_file)
      (write-line "            }" dcl_file)
      (write-line "            : edit_box {" dcl_file)
      (write-line "                key = \"adv_textgap\";" dcl_file)
      (write-line "                edit_width = 10;" dcl_file)
      (write-line "            }" dcl_file)
      (write-line "        }" dcl_file)
      (write-line "    }" dcl_file)
      (write-line "    " dcl_file)
      (write-line "    : boxed_column {" dcl_file)
      (write-line "        label = \"화살표 설정\";" dcl_file)
      (write-line "        : row {" dcl_file)
      (write-line "            : text {" dcl_file)
      (write-line "                label = \"화살표 크기 (DIMASZ):\";" dcl_file)
      (write-line "                width = 25;" dcl_file)
      (write-line "            }" dcl_file)
      (write-line "            : edit_box {" dcl_file)
      (write-line "                key = \"adv_arrowsize\";" dcl_file)
      (write-line "                edit_width = 10;" dcl_file)
      (write-line "            }" dcl_file)
      (write-line "        }" dcl_file)
      (write-line "    }" dcl_file)
      (write-line "    " dcl_file)
      (write-line "    : boxed_column {" dcl_file)
      (write-line "        label = \"치수보조선 설정\";" dcl_file)
      (write-line "        : row {" dcl_file)
      (write-line "            : text {" dcl_file)
      (write-line "                label = \"간격띄우기 (DIMEXO):\";" dcl_file)
      (write-line "                width = 25;" dcl_file)
      (write-line "            }" dcl_file)
      (write-line "            : edit_box {" dcl_file)
      (write-line "                key = \"adv_extoffset\";" dcl_file)
      (write-line "                edit_width = 10;" dcl_file)
      (write-line "            }" dcl_file)
      (write-line "        }" dcl_file)
      (write-line "        : row {" dcl_file)
      (write-line "            : text {" dcl_file)
      (write-line "                label = \"보조선 연장 (DIMEXE):\";" dcl_file)
      (write-line "                width = 25;" dcl_file)
      (write-line "            }" dcl_file)
      (write-line "            : edit_box {" dcl_file)
      (write-line "                key = \"adv_extextend\";" dcl_file)
      (write-line "                edit_width = 10;" dcl_file)
      (write-line "            }" dcl_file)
      (write-line "        }" dcl_file)
      (write-line "    }" dcl_file)
      (write-line "    " dcl_file)
      (write-line "    spacer;" dcl_file)
      (write-line "    " dcl_file)
      (write-line "    : row {" dcl_file)
      (write-line "        : spacer { width = 1; }" dcl_file)
      (write-line "        : button {" dcl_file)
      (write-line "            key = \"accept\";" dcl_file)
      (write-line "            label = \"확인\";" dcl_file)
      (write-line "            is_default = true;" dcl_file)
      (write-line "            fixed_width = true;" dcl_file)
      (write-line "            width = 12;" dcl_file)
      (write-line "        }" dcl_file)
      (write-line "        : button {" dcl_file)
      (write-line "            key = \"cancel\";" dcl_file)
      (write-line "            label = \"취소\";" dcl_file)
      (write-line "            is_cancel = true;" dcl_file)
      (write-line "            fixed_width = true;" dcl_file)
      (write-line "            width = 12;" dcl_file)
      (write-line "        }" dcl_file)
      (write-line "        : spacer { width = 1; }" dcl_file)
      (write-line "    }" dcl_file)
      (write-line "}" dcl_file)
      
      (close dcl_file)
      (princ (strcat "\nDCL 파일 생성됨: " dcl_path))
      dcl_path ; DCL 파일 경로 반환
    )
    (progn
      (princ "\nDCL 파일 생성 실패!")
      nil
    )
  )
)

;;;; ============================================================================
;;;; 메인 명령어 함수
;;;; ============================================================================
(defun C:DM (/ dcl_id result dimstyle-name dcl_path base_scale)
  (princ "\n치수 스타일 생성 프로그램 시작...")
  
  ;; DCL 파일 자동 생성
  (setq dcl_path (create_dcl_file))
  
  (if (or (not dcl_path) (not (findfile dcl_path)))
    (progn
      (alert "DCL 파일을 생성하거나 찾을 수 없습니다!")
      (exit)
    )
  )
  
  ;; DCL 파일 로드
  (setq dcl_id (load_dialog dcl_path))
  
  (if (not dcl_id)
    (progn
      (alert (strcat "DCL 대화상자를 로드할 수 없습니다!\n경로: " dcl_path))
      (exit)
    )
  )
  
  (if (not (new_dialog "dimstyle" dcl_id))
    (progn
      (unload_dialog dcl_id)
      (alert "DCL 대화상자를 초기화할 수 없습니다!")
      (exit)
    )
  )
  
  ;; 기본 축척 설정 (마지막 사용 값 불러오기)
  (setq *dim_scale* *last_dim_scale*)  ; 마지막 사용 축척
  (setq *dim_distance* *last_dim_distance*)  ; 마지막 사용 치수선 거리
  
  ;; ISO-25 표준 기준값 (축척 1:20 기준)
  (setq base_scale 20.0)           ; 기준 축척
  (setq base_text_height 3.0)      ; 기준 문자 높이
  (setq base_arrow_size 2.5)       ; 기준 화살표 크기
  (setq base_ext_offset 10.0)      ; 기준 치수보조선 간격
  (setq base_ext_extend 1.25)      ; 기준 치수보조선 연장
  (setq base_text_gap 0.625)       ; 기준 문자 간격
  
  ;; DCL 컨트롤 초기화
  (set_tile "dimscale" *dim_scale*)
  (set_tile "dim_distance_display" *dim_distance*)
  
  ;; 치수 타입 라디오 버튼 초기화 (항상 정렬된 치수가 기본)
  (set_tile "dim_aligned" "1")  ; 정렬된 치수 기본 선택
  (setq *dim_type* "1")          ; 기본값: 정렬된 치수
  
  ;; 계산된 값들을 표시 (사용자 정의값이 있으면 사용, 없으면 자동 계산)
  (if *custom_text_height*
    (set_tile "textheight" (rtos (atof *custom_text_height*) 2 2))
    (set_tile "textheight" (rtos base_text_height 2 2))
  )
  (if *custom_arrow_size*
    (set_tile "arrowsize" (rtos (atof *custom_arrow_size*) 2 2))
    (set_tile "arrowsize" (rtos base_arrow_size 2 2))
  )
  (if *custom_ext_offset*
    (set_tile "extoffset" (rtos (atof *custom_ext_offset*) 2 2))
    (set_tile "extoffset" (rtos base_ext_offset 2 2))
  )
  (if *custom_ext_extend*
    (set_tile "extextend" (rtos (atof *custom_ext_extend*) 2 2))
    (set_tile "extextend" (rtos base_ext_extend 2 2))
  )
  (if *custom_text_gap*
    (set_tile "textgap" (rtos (atof *custom_text_gap*) 2 3))
    (set_tile "textgap" (rtos base_text_gap 2 3))
  )
  
  ;; 액션 설정 - 치수 타입 선택
  (action_tile "dim_linear" "(setq *dim_type* \"0\")")
  (action_tile "dim_aligned" "(setq *dim_type* \"1\")")
  
  ;; 액션 설정 - 전체 축척 변경 시 모든 값 재계산 (사용자 정의값이 없을 때만)
  (action_tile "dimscale" 
    "(progn
       (setq *dim_scale* $value)
       (if (not *custom_text_height*)
         (progn
           (setq scale_ratio (/ (atof *dim_scale*) base_scale))
           (set_tile \"textheight\" (rtos (* base_text_height scale_ratio) 2 2))
           (set_tile \"arrowsize\" (rtos (* base_arrow_size scale_ratio) 2 2))
           (set_tile \"extoffset\" (rtos (* base_ext_offset scale_ratio) 2 2))
           (set_tile \"extextend\" (rtos (* base_ext_extend scale_ratio) 2 2))
           (set_tile \"textgap\" (rtos (* base_text_gap scale_ratio) 2 3))
         )
       )
     )"
  )
  
  ;; 액션 설정 - 치수선 거리 변경
  (action_tile "dim_distance" "(setq *dim_distance* $value)")
  
  ;; 액션 설정 - 지시선 버튼
  (action_tile "create_leader" "(setq result 3) (done_dialog 3)")
  
  ;; 액션 설정 - 수정 버튼
  (action_tile "edit_advanced" "(setq result 2) (done_dialog 2)")
  
  ;; 액션 설정 - 리셋 버튼
  (action_tile "reset"
    "(progn
       (setq *dim_scale* \"20\")
       (setq *dim_distance* \"400\")
       (setq *custom_text_height* nil)
       (setq *custom_arrow_size* nil)
       (setq *custom_ext_offset* nil)
       (setq *custom_ext_extend* nil)
       (setq *custom_text_gap* nil)
       (set_tile \"dimscale\" \"20\")
       (set_tile \"dim_distance\" \"400\")
       (set_tile \"textheight\" (rtos base_text_height 2 2))
       (set_tile \"arrowsize\" (rtos base_arrow_size 2 2))
       (set_tile \"extoffset\" (rtos base_ext_offset 2 2))
       (set_tile \"extextend\" (rtos base_ext_extend 2 2))
       (set_tile \"textgap\" (rtos base_text_gap 2 3))
       (princ \"\\n\\uae30\\ubcf8\\uac12\\uc73c\\ub85c \\ub9ac\\uc14b\\ub418\\uc5c8\\uc2b5\\ub2c8\\ub2e4.\")
     )"
  )
  
  (action_tile "accept" "(done_dialog 1)")
  (action_tile "cancel" "(done_dialog 0)")
  
  ;; 대화상자 표시 및 루프 (수정 버튼 처리)
  (setq result (start_dialog))
  
  ;; 지시선 버튼을 누른 경우 (result = 3)
  (if (= result 3)
    (progn
      ;; 지시선 스타일 생성 및 적용 후 대화상자로 돌아가기
      (unload_dialog dcl_id)
      
      ;; 마지막 사용 축척 및 거리 저장
      (setq *last_dim_scale* *dim_scale*)
      (setq *last_dim_distance* *dim_distance*)
      
      ;; 비율 계산
      (setq scale_ratio (/ (atof *dim_scale*) base_scale))
      
      (if *custom_text_height*
        (setq *dim_text_height* *custom_text_height*)
        (setq *dim_text_height* (rtos (* base_text_height scale_ratio) 2 2))
      )
      (if *custom_arrow_size*
        (setq *dim_arrow_size* *custom_arrow_size*)
        (setq *dim_arrow_size* (rtos (* base_arrow_size scale_ratio) 2 2))
      )
      
      ;; MLEADER 스타일 생성
      (create_mleader_style "ISO-25-Custom")
      
      ;; 지시선 그리기
      (princ "\n지시선 그리기 모드...")
      (command "._MLEADER")
      
      ;; 완료 메시지
      (princ "\n지시선 그리기 완료.")
      (princ)
      (exit)
    )
  )
  
  ;; 수정 버튼을 누른 경우 (result = 2)
  (while (= result 2)
    ;; 고급 설정 대화상자 열기
    (if (not (new_dialog "advanced_settings" dcl_id))
      (progn
        (alert "고급 설정 대화상자를 열 수 없습니다!")
        (setq result 0)
      )
      (progn
        ;; 현재 값으로 초기화 (사용자 정의값이 있으면 사용, 없으면 자동 계산값)
        (setq scale_ratio (/ (atof *dim_scale*) base_scale))
        
        (if *custom_text_height*
          (set_tile "adv_textheight" *custom_text_height*)
          (set_tile "adv_textheight" (rtos (* base_text_height scale_ratio) 2 2))
        )
        (if *custom_arrow_size*
          (set_tile "adv_arrowsize" *custom_arrow_size*)
          (set_tile "adv_arrowsize" (rtos (* base_arrow_size scale_ratio) 2 2))
        )
        (if *custom_ext_offset*
          (set_tile "adv_extoffset" *custom_ext_offset*)
          (set_tile "adv_extoffset" (rtos (* base_ext_offset scale_ratio) 2 2))
        )
        (if *custom_ext_extend*
          (set_tile "adv_extextend" *custom_ext_extend*)
          (set_tile "adv_extextend" (rtos (* base_ext_extend scale_ratio) 2 2))
        )
        (if *custom_text_gap*
          (set_tile "adv_textgap" *custom_text_gap*)
          (set_tile "adv_textgap" (rtos (* base_text_gap scale_ratio) 2 3))
        )
        
        ;; 치수선 거리 (Y값) 초기화
        (set_tile "adv_distance" *dim_distance*)
        
        ;; 고급 설정 확인 버튼
        (action_tile "accept"
          "(progn
             (setq *dim_distance* (get_tile \"adv_distance\"))
             (setq *custom_text_height* (get_tile \"adv_textheight\"))
             (setq *custom_arrow_size* (get_tile \"adv_arrowsize\"))
             (setq *custom_ext_offset* (get_tile \"adv_extoffset\"))
             (setq *custom_ext_extend* (get_tile \"adv_extextend\"))
             (setq *custom_text_gap* (get_tile \"adv_textgap\"))
             (done_dialog 3)
           )"
        )
        (action_tile "cancel" "(done_dialog 0)")
        
        (setq adv_result (start_dialog))
        
        ;; 고급 설정 확인 후 메인 다이얼로그로 돌아가기
        (if (= adv_result 3)
          (progn
            ;; 메인 다이얼로그 다시 열기
            (if (not (new_dialog "dimstyle" dcl_id))
              (progn
                (alert "DCL 대화상자를 다시 열 수 없습니다!")
                (setq result 0)
              )
              (progn
                ;; 메인 다이얼로그 재초기화
                (set_tile "dimscale" *dim_scale*)
                (set_tile "dim_distance_display" *dim_distance*)
                (set_tile "dim_aligned" "1")
                (setq *dim_type* "1")
                
                ;; 업데이트된 값 표시
                (set_tile "textheight" (rtos (atof *custom_text_height*) 2 2))
                (set_tile "arrowsize" (rtos (atof *custom_arrow_size*) 2 2))
                (set_tile "extoffset" (rtos (atof *custom_ext_offset*) 2 2))
                (set_tile "extextend" (rtos (atof *custom_ext_extend*) 2 2))
                (set_tile "textgap" (rtos (atof *custom_text_gap*) 2 3))
                
                ;; 액션 재설정
                (action_tile "dim_linear" "(setq *dim_type* \"0\")")
                (action_tile "dim_aligned" "(setq *dim_type* \"1\")")
                (action_tile "dimscale" "(setq *dim_scale* $value)")
                (action_tile "edit_advanced" "(setq result 2) (done_dialog 2)")
                (action_tile "reset"
                  "(progn
                     (setq *dim_scale* \"20\")
                     (setq *dim_distance* \"400\")
                     (setq *custom_text_height* nil)
                     (setq *custom_arrow_size* nil)
                     (setq *custom_ext_offset* nil)
                     (setq *custom_ext_extend* nil)
                     (setq *custom_text_gap* nil)
                     (set_tile \"dimscale\" \"20\")
                     (set_tile \"dim_distance\" \"400\")
                     (set_tile \"textheight\" (rtos base_text_height 2 2))
                     (set_tile \"arrowsize\" (rtos base_arrow_size 2 2))
                     (set_tile \"extoffset\" (rtos base_ext_offset 2 2))
                     (set_tile \"extextend\" (rtos base_ext_extend 2 2))
                     (set_tile \"textgap\" (rtos base_text_gap 2 3))
                     (princ \"\\n\\uae30\\ubcf8\\uac12\\uc73c\\ub85c \\ub9ac\\uc14b\\ub418\\uc5c8\\uc2b5\\ub2c8\\ub2e4.\")
                   )"
                )
                (action_tile "accept" "(done_dialog 1)")
                (action_tile "cancel" "(done_dialog 0)")
                
                (setq result (start_dialog))
              )
            )
          )
          (setq result 0)  ; 고급 설정 취소 시
        )
      )
    )
  )
  
  (unload_dialog dcl_id)
  
  ;; (wcmatch "비교문자열" "패턴") - 와일드카드 비교
  (if (not (wcmatch (strcase (vl-filename-base dcl_path)) "DIMSTYLE"))
    (if (findfile dcl_path)
      (progn
        (vl-file-delete dcl_path)
        (princ (strcat "\n임시 DCL 파일 삭제됨: " dcl_path))
      )
    )
    (princ (strcat "\nDCL 파일 유지됨: " dcl_path))
  )
  
  ;; 사용자가 확인을 누른 경우
  (if (= result 1)
    (progn
      (princ "\n치수 스타일 생성 중...")
      
      ;; '!-치수' 레이어 확인 및 생성 (빨간색: 1)
      (ensure_layer "!-치수" 1)
      
      ;; 현재 레이어를 '!-치수'로 변경
      (setvar "CLAYER" "!-치수")
      (princ "\n현재 레이어: !-치수")
      
      ;; 마지막 사용 축척 및 거리 저장
      (setq *last_dim_scale* *dim_scale*)
      (setq *last_dim_distance* *dim_distance*)
      
      ;; 비율에 따라 모든 값 계산 (사용자 정의값이 있으면 사용, 없으면 자동 계산)
      (setq scale_ratio (/ (atof *dim_scale*) base_scale))
      
      (if *custom_text_height*
        (setq *dim_text_height* *custom_text_height*)
        (setq *dim_text_height* (rtos (* base_text_height scale_ratio) 2 2))
      )
      (if *custom_arrow_size*
        (setq *dim_arrow_size* *custom_arrow_size*)
        (setq *dim_arrow_size* (rtos (* base_arrow_size scale_ratio) 2 2))
      )
      (if *custom_ext_offset*
        (setq *dim_ext_offset* *custom_ext_offset*)
        (setq *dim_ext_offset* (rtos (* base_ext_offset scale_ratio) 2 2))
      )
      (if *custom_ext_extend*
        (setq *dim_ext_extend* *custom_ext_extend*)
        (setq *dim_ext_extend* (rtos (* base_ext_extend scale_ratio) 2 2))
      )
      (if *custom_text_gap*
        (setq *dim_text_gap* *custom_text_gap*)
        (setq *dim_text_gap* (rtos (* base_text_gap scale_ratio) 2 3))
      )
      
      ;; 치수 스타일 생성
      (setq dimstyle-name "ISO-25-Custom")
      (create_dimstyle dimstyle-name)
      
      ;; MLEADER 스타일 생성
      (create_mleader_style dimstyle-name)
      
      ;; 연속 치수 그리기 (루프)
      (princ "\n치수 그리기 시작... (ESC로 종료)")
      (princ (strcat "\n현재 치수 스타일: " dimstyle-name))
      (princ (strcat "\n전체 축척: " *dim_scale*))
      
      ;; 연속 치수 그리기 루프
      (setq continue_loop T)
      (while continue_loop
        ;; 치수 그리기 (세 점 입력: pt1, pt2, pt3-방향)
        (setq pt1 (getpoint "\n첫 번째 치수보조선 원점 또는 [ESC 종료]: "))
        
        (if pt1
          (progn
            (setq pt2 (getpoint pt1 "\n두 번째 치수보조선 원점: "))
            
            (if pt2
              (progn
                ;; pt3: 치수선 방향 지정 (DIM 명령어의 마우스 방향과 동일)
                (setq pt3 (getpoint pt2 "\n치수선 방향 지정: "))
                
                (if pt3
                  (progn
                    ;; pt1-pt2 벡터 계산
                    (setq dx (- (car pt2) (car pt1)))
                    (setq dy (- (cadr pt2) (cadr pt1)))
                    (setq dist (sqrt (+ (* dx dx) (* dy dy))))
                    
                    (if (> dist 0.001)
                      (progn
                        ;; pt1-pt2의 단위 벡터
                        (setq unit_x (/ dx dist))
                        (setq unit_y (/ dy dist))
                        
                        ;; pt1-pt2에 수직인 벡터 (기본: 왼쪽 방향)
                        (setq perp_x (- unit_y))
                        (setq perp_y unit_x)
                        
                        ;; pt1-pt2의 중간점
                        (setq mid_x (/ (+ (car pt1) (car pt2)) 2.0))
                        (setq mid_y (/ (+ (cadr pt1) (cadr pt2)) 2.0))
                        
                        ;; 중간점에서 pt3으로의 벡터
                        (setq to_pt3_x (- (car pt3) mid_x))
                        (setq to_pt3_y (- (cadr pt3) mid_y))
                        
                        ;; pt3이 수직선의 어느 쪽에 있는지 판단 (내적 사용)
                        ;; 내적 = perp_x * to_pt3_x + perp_y * to_pt3_y
                        ;; 양수: pt3이 perp 방향과 같은 쪽
                        ;; 음수: pt3이 perp 방향과 반대 쪽
                        (setq dot_product (+ (* perp_x to_pt3_x) (* perp_y to_pt3_y)))
                        
                        ;; pt3 방향에 따라 수직 벡터의 방향 결정
                        (if (< dot_product 0)
                          (progn
                            ;; 반대 방향으로 전환
                            (setq perp_x (- perp_x))
                            (setq perp_y (- perp_y))
                          )
                        )
                        
                        ;; 중간점에서 수직 방향으로 사용자 지정 거리만큼 떨어진 위치
                        (setq dim_pt (list 
                          (+ mid_x (* perp_x (atof *dim_distance*)))
                          (+ mid_y (* perp_y (atof *dim_distance*)))
                        ))
                        
                        ;; 선택된 치수 타입에 따라 명령어 실행
                        (if (= *dim_type* "0")
                          (progn
                            ;; 회전된 치수 (DIMLINEAR)
                            (command "._DIMLINEAR" pt1 pt2 dim_pt)
                            (princ "\n회전된 치수 생성 완료. 다음 치수를 계속 그립니다...")
                          )
                          (progn
                            ;; 정렬된 치수 (DIMALIGNED)
                            (command "._DIMALIGNED" pt1 pt2 dim_pt)
                            (princ "\n정렬된 치수 생성 완료. 다음 치수를 계속 그립니다...")
                          )
                        )
                      )
                      (princ "\n두 점이 너무 가깝습니다.")
                    )
                  )
                  ;; pt3가 nil이면 사용자가 ESC를 누름
                  (progn
                    (princ "\n치수 그리기 취소.")
                    (setq continue_loop nil)
                  )
                )
              )
              ;; pt2가 nil이면 사용자가 ESC를 누름
              (progn
                (princ "\n치수 그리기 종료.")
                (setq continue_loop nil)
              )
            )
          )
          ;; pt1이 nil이면 사용자가 ESC를 누르거나 Enter를 누름
          (progn
            (princ "\n치수 그리기 종료.")
            (setq continue_loop nil)
          )
        )
      )
    )
    (princ "\n취소되었습니다.")
  )
  
  (princ)
)

;;;; ============================================================================
;;;; MLEADER 스타일 생성 함수
;;;; ============================================================================
(defun create_mleader_style (style-name / old_cmdecho old_osmode result)
  (princ (strcat "\nMLEADER 스타일 '" style-name "' 생성 중..."))
  
  ;; 명령 에코 및 OSMODE 끄기
  (setq old_cmdecho (getvar "CMDECHO"))
  (setq old_osmode (getvar "OSMODE"))
  (setvar "CMDECHO" 0)
  (setvar "OSMODE" 0)
  
  ;; MLEADER 스타일 생성 (Standard 기반 복사)
  ;; tblsearch는 MLEADERSTYLE 테이블을 지원하지 않으므로
  ;; 그냥 생성하고 이미 존재하면 무시됨
  (setq result (vl-catch-all-apply 'command 
    (list "._-MLEADERSTYLE" "_N" style-name "_C" "Standard" "")
  ))
  
  (if (vl-catch-all-error-p result)
    (princ (strcat "\nMLEADER 스타일 '" style-name "' 이미 존재함 (계속)"))
    (princ (strcat "\nMLEADER 스타일 '" style-name "' 생성됨"))
  )
  
  ;; 생성된 스타일을 현재 스타일로 설정
  (command "._-MLEADERSTYLE" "_R" style-name)
  
  ;; 명령 에코 및 OSMODE 복원
  (setvar "CMDECHO" old_cmdecho)
  (setvar "OSMODE" old_osmode)
  
  (princ "\n=== MLEADER 스타일 생성 완료 ===")
  (princ (strcat "\n  스타일 이름: " style-name))
  (princ (strcat "\n  (치수 스타일 " style-name "과 이름만 같고 별개 스타일)"))
  (princ)
)

;;;; ============================================================================
;;;; 레이어 생성/확인 함수
;;;; ============================================================================
(defun ensure_layer (layer-name layer-color / layer-table layer-obj)
  ;; 레이어가 존재하는지 확인
  (if (not (tblsearch "LAYER" layer-name))
    (progn
      ;; 레이어가 없으면 새로 생성
      (command "._-LAYER" "_N" layer-name "_C" layer-color layer-name "")
      (princ (strcat "\n레이어 '" layer-name "' 생성됨 (색상: " (itoa layer-color) ")"))
    )
    (princ (strcat "\n레이어 '" layer-name "' 이미 존재함"))
  )
)

;;;; ============================================================================
;;;; 치수 스타일 생성 함수 - ISO-25 전체 설정
;;;; ============================================================================
(defun create_dimstyle (style-name /)
  
  ;; ========================================
  ;; [1] 선(Line) 탭 설정
  ;; ========================================
  
  ;; 치수선 설정
  (setvar "DIMCLRD" 256)                 ; 치수선 색상: ByLayer
  (setvar "DIMDLE" 0.0)                  ; 눈금 너머로 연장: 0
  (setvar "DIMDLI" 3.75)                 ; 기준선 간격: 3.75
  
  ;; 치수보조선 설정
  (setvar "DIMCLRE" 256)                 ; 치수보조선 색상: ByLayer
  (setvar "DIMEXE" (atof *dim_ext_extend*))   ; 치수선 너머로 연장: 1.25
  (setvar "DIMEXO" (atof *dim_ext_offset*))   ; 원점에서 간격띄우기: 0.625
  (setvar "DIMSE1" 0)                    ; 첫번째 치수보조선 표시
  (setvar "DIMSE2" 0)                    ; 두번째 치수보조선 표시
  
  ;; ========================================
  ;; [2] 화살표(Symbols) 탭 설정
  ;; ========================================
  
  ;; 화살촉 설정
  (setvar "DIMBLK" "")                    ; 첫 번째: 닫힌 채움 (기본값 = 빈 문자열)
  (setvar "DIMBLK1" "")                   ; 두 번째: 닫힌 채움
  (setvar "DIMBLK2" "")                   ; 지시선: 닫힌 채움
  (setvar "DIMASZ" (atof *dim_arrow_size*)) ; 화살표 크기: 2.5
  
  ;; 중심 표시
  (setvar "DIMCEN" 2.5)                  ; 중심 표시 크기: 2.5 (양수 = 표식)
  
  ;; ========================================
  ;; [3] 문자(Text) 탭 설정
  ;; ========================================
  
  ;; 문자 모양
  (setvar "DIMTXSTY" "Standard")         ; 문자 스타일: Standard
  (setvar "DIMCLRT" 7)                   ; 문자 색상: 흰색 (7)
  (setvar "DIMTXT" (atof *dim_text_height*)) ; 문자 높이: 3
  (setvar "DIMTFAC" 1.0)                 ; 분수 높이 축척: 1
  
  ;; 문자 배치
  (setvar "DIMTAD" 1)                    ; 수직: 위 (1)
  (setvar "DIMJUST" 0)                   ; 수평: 중심 (0)
  (setvar "DIMGAP" (atof *dim_text_gap*))  ; 치수선에 관계없이: 0.625
  
  ;; 문자 정렬
  (setvar "DIMTIH" 0)                    ; 치수선에 정렬 (내부 수평: 끄기)
  (setvar "DIMTOH" 0)                    ; 치수선에 정렬 (외부 수평: 끄기)
  
  ;; ========================================
  ;; [4] 맞춤(Fit) 탭 설정
  ;; ========================================
  
  ;; 맞춤 옵션
  (setvar "DIMATFIT" 2)                 ; 화살표를 먼저 이동 (2)
  
  ;; 문자 배치
  (setvar "DIMTMOVE" 1)                 ; 문자가 기본 위치에 없을 경우: 치수선 위에 지시선 추가 (1)
  
  ;; 치수 축척
  (setvar "DIMSCALE" (atof *dim_scale*))   ; 전체 축척: 20
  
  ;; 최소으로 조정
  (setvar "DIMTOFL" 1)                   ; 치수보조선 사이에 치수선 그리기: 1 (켜짐)
  
  ;; ========================================
  ;; [5] 1차 단위(Primary Units) 탭 설정
  ;; ========================================
  
  ;; 선형 치수
  (setvar "DIMLUNIT" 6)                 ; 단위 형식: 십진법 + 천 단위 구분 기호 (6)
  (setvar "DIMDEC" 2)                   ; 정밀도: 0.00 (소수점 2자리)
  
  ;; [수정] 소수 구분 기호 (정수 0이 아닌 문자열 "."로 설정)
  ;; (ascii ".")는 46을 반환하여 오류 발생.
  ;; setvar로 DIMDSEP를 설정할 때는 예외적으로 문자열을 사용해야 합니다.
  (setvar "DIMDSEP" ".")                   ; 소수 구분 기호: . (점)
  
  (setvar "DIMRND" 0)                    ; 반올림: 0
  
  ;; 측정 축척
  (setvar "DIMLFAC" 1.0)                 ; 비율: 1
  
  ;; [수정] 0 억제
  ;; 12 (8+4)는 선행 0 (.5)과 후행 0 (12.5)을 모두 억제합니다.
  ;; ISO 표준은 선행 0을 표시(0.5)하므로, 후행 0만 억제하는 8을 사용합니다.
  (setvar "DIMZIN" 8)                    ; 후행 0 억제 (8)
  
  ;; 각도 치수
  (setvar "DIMAUNIT" 0)                 ; 단위 형식: 십진 도수 (0)
  (setvar "DIMADEC" 0)                  ; 정밀도: 0
  (setvar "DIMAZIN" 0)                  ; 각도 0 억제: 없음
  
  ;; ========================================
  ;; [6] 대체 단위(Alternate Units) 탭 설정
  ;; ========================================
  
  ;; 대체 단위 표시
  (setvar "DIMALT" 0)                    ; 대체 단위 표시: 끄기 (0)
  (setvar "DIMALTF" 0.03937007)          ; 대체 단위 승수: mm to inch
  (setvar "DIMALTD" 3)                   ; 대체 단위 정밀도: 0.000
  (setvar "DIMALTRND" 0)                 ; 반올림: 0
  
  ;; ========================================
  ;; [7] 공차(Tolerances) 탭 설정
  ;; ========================================
  
  ;; 공차 형식
  (setvar "DIMTOL" 0)                    ; 공차 표시: 없음 (0)
  (setvar "DIMTP" 0)                     ; 상한값: 0
  (setvar "DIMTM" 0)                     ; 하한값: 0
  (setvar "DIMTFAC" 1.0)                 ; 높이에 대한 축척: 1
  (setvar "DIMTOLJ" 0)                   ; 수직 위치: 맨 아래 (0)
  
  ;; 대체 단위 공차
  (setvar "DIMALTD" 3)                   ; 정밀도: 0.000
  
  ;; ========================================
  ;; 치수 스타일 저장 및 적용
  ;; ========================================
  
  ;; [수정] (setvar)로 변수만 설정하면 현재 스타일에만 적용됩니다.
  ;; (command)를 사용하기 전에 (setvar)를 사용하면
  ;; -DIMSTYLE -> S(저장) 명령이 현재 설정된 변수값을 
  ;; "style-name"으로 저장하게 됩니다.
  
  ;; 치수 스타일이 이미 있는지 확인
  (if (tblsearch "DIMSTYLE" style-name)
    (progn
      ;; 있으면 덮어쓰기
      (command "._-DIMSTYLE" "_S" style-name "_Y")
    )
    (progn
      ;; 없으면 새로 생성 (현재 설정값 기준)
      (command "._-DIMSTYLE" "_S" style-name)
    )
  )
  
  ;; 새로 만든 스타일을 현재 스타일로 설정
  (command "._-DIMSTYLE" "_R" style-name)
  
  (princ (strcat "\n치수 스타일 '" style-name "' 생성 완료!"))
  (princ "\n=== ISO-25 표준 설정 적용됨 ===")
  (princ (strcat "\n  전체 축척: " *dim_scale*))
  (princ (strcat "\n  문자 높이: " *dim_text_height*))
  (princ (strcat "\n  화살표 크기: " *dim_arrow_size*))
  (princ)
)



;;;; ============================================================================
;;;; 프로그램 로드 메시지
;;;; ============================================================================
(princ "\nDM 로드됨")
(if *last_dim_scale*
  (princ (strcat " (마지막 축척: " *last_dim_scale* ")"))
)
(princ)
